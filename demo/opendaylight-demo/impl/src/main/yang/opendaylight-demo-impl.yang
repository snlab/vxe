module vxe-opendaylight-demo-impl {
    yang-version 1;
    namespace "urn:vxe:demo:opendaylight:impl";
    prefix "vxe-opendaylight-demo-impl";

    import config { prefix config; revision-date 2013-04-05; }
    import opendaylight-md-sal-binding { prefix md-sal-binding; revision-date 2013-10-28;}

    import opendaylight-sal-binding-broker-impl {
        prefix md-sal-binding-impl;
        revision-date 2013-10-28;
    }

    description
        "Service definition for opendaylight-demo project";

    revision "2016-04-08" {
        description
            "Initial revision";
    }

    identity opendaylight-demo {
        base config:module-type;
        config:java-name-prefix VxeOpenDaylightDemo;
    }

    augment "/config:modules/config:module/config:configuration" {
        case opendaylight-demo {
            when "/config:modules/config:module/config:type = 'opendaylight-demo'";
            container broker {
                uses config:service-ref {
                    refine type {
                        mandatory true;
                        config:required-identity md-sal-binding:binding-broker-osgi-registry;
                    }
                }
            }

            container binding-mapping-service {
                uses config:service-ref {
                    refine type {
                        mandatory true;
                        config:required-identity md-sal-binding-impl:binding-dom-mapping-service;
                    }
                }
            }
        }
    }
}
